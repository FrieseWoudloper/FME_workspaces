FME workspace BAGResponsePaging.fmw

Parameters:
- MaxFeatures = 1000   # Het maximum aantal features dat de WFS per request retourneert
- BaseURL = http://geodata.nationaalgeoregister.nl/bag/wfs?   # URL van de WFS-service
- FeatureType = bag:verblijfsobject   # FeatureType dat ingelezen moeten worden
- Filter = (bag:woonplaats='Groningen')   # CQL-filter voor het service request
- SRS = EPSG:28992   # Coördinatenstelsel waarin de service geometrie moet retourneren
- SortBy = bag:identificatie   # Attribuut waarop het resulaat van het service request gesorteerd moet worden
- Attributen = identificatie oppervlakte status gebruiksdoel openbare_ruimte huisnummer huisletter toevoeging postcode woonplaats actualiteitsdatum bouwjaar pandstatus pandidentificatie geometrie.Point.pos   # Attributen uit GML-respons die bewaard moeten blijven
- Node = bag:verblijfsobject   # " " Node in GML-output die attributen en geometrie bevat

AttributeKeeper_2_Output: Inspector

Bookmark: Het aantal features bepalen dat door de service geretourneerd wordt
Creator
    NUM = 1
    GEOMTYPE = Geometry Object
    CREATED -> HTTPCaller
HTTPCaller
    FOLLOW_REDIRECTS = Yes
    TARGET_ATTR_ENCODING = auto-detect
    TARGET_ATTR = _response_body
    STATUS_CODE_ATTR = _http_status_code
    VERIFY_SSL_CERTIFICATES = Yes
    SAVE_FILE = Attribute
    RESPONSE_HEADER_LIST_ATTR = _headers
    USE_COOKIES = No
    TARGET_URL = $(BaseURL)
    TRANSFER_TIMEOUT_LENGTH = 90
    ADDITIONAL_URL_PARAMETERS = service;WFS version;2.0.0 request;GetFeature srs;$(SRS) typename;$(FeatureType) cql_filter;$(Filter) resulttype;hits
    CONNECTION_TIMEOUT_LENGTH = 60
    HTTP_METHOD = GET
    ERROR_ATTR = _error
    -> XMLFlattener
XMLFlattener
    ATTRIBUTE_XML = _response_body
    XML_SOURCE_TYPE = Attribute with XML document
    NEW_ATTRIBUTES = FeatureCollection.numberMatched
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    EMBEDDED_EXPRESSIONS = wfs:FeatureCollection
    -> AttributeKeeper
AttributeKeeper
    KEEP_ATTRS = FeatureCollection.numberMatched
    -> AttributeRenamer
AttributeRenamer
    ATTR_LIST = FeatureCollection.numberMatched,AantalFeatures,
    -> ExpressionEvaluator

Bookmark: Response paging
Note: Het aantal requests dat nodig is
ExpressionEvaluator
    VAL_ATTR = AantalRequests
    ACTION = Create New Attribute
    EXPRESSION = @ceil(@Evaluate(@Value(AantalFeatures)/$(MaxFeatures)))
    -> Cloner
Cloner
    COPIES = @Value(AantalRequests)
    COPYATT = StartIndex
    COPY -> ExpressionEvaluator_2
Note: De parameterwaarde StartIndex voor ieder request
ExpressionEvaluator_2
    ACTION = Overwrite Existing Attributes
    ATTRLIST = StartIndex
    EXPRESSION = @Evaluate(@Value(StartIndex)*$(MaxFeatures))
    -> HTTPCaller_2
Note: GetFeature requests
HTTPCaller_2
    FOLLOW_REDIRECTS = Yes
    TARGET_ATTR_ENCODING = auto-detect
    TARGET_ATTR = _response_body
    STATUS_CODE_ATTR = _http_status_code
    VERIFY_SSL_CERTIFICATES = Yes
    SAVE_FILE = Attribute
    RESPONSE_HEADER_LIST_ATTR = _headers
    USE_COOKIES = No
    TARGET_URL = $(BaseURL)
    TRANSFER_TIMEOUT_LENGTH = 90
    ADDITIONAL_URL_PARAMETERS = service;wfs version;2.0.0 request;GetFeature typename;$(FeatureType) srs;$(SRS) cql_filter;$(Filter) startindex;@Value(StartIndex) count;$(MaxFeatures) sortby;$(SortBy) A
    CONNECTION_TIMEOUT_LENGTH = 60
    HTTP_METHOD = GET
    ERROR_ATTR = _error
    -> XMLFragmenter

Bookmark: Respons van de WFS-service omzetten naar features
XMLFragmenter
    ATTRIBUTE_XML = _response_body
    XML_SOURCE_TYPE = Attribute with XML document
    FEATURE_TYPES_FORMAT_NAME = XML
    EMBEDDED_EXPRESSIONS = $(Node)
    MERGE_ATTRS = No
    FRAGMENTS -> XMLFlattener_2
XMLFlattener_2
    ATTRIBUTE_XML = xml_fragment
    XML_SOURCE_TYPE = Attribute with XML document
    NEW_ATTRIBUTES = $(Attributen)
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    EMBEDDED_EXPRESSIONS = $(Node)
    -> AttributeSplitter
AttributeSplitter
    LIST_NAME = pos
    DELIMITER = " "
    DROP_EMPTY_PARTS = No
    ATTR_NAME = geometrie.Point.pos
    TRIM_OPTION = Both
    -> VertexCreator
VertexCreator
    YVAL = @Value(pos{1})
    MODE_NAME = Add Point
    INDEX = 0
    XVAL = @Value(pos{0})
    -> AttributeKeeper_2
AttributeKeeper_2
    KEEP_ATTRS = bouwjaar,identificatie,huisnummer,openbare_ruimte,pandidentificatie,actualiteitsdatum,gebruiksdoel,toevoeging,status,woonplaats,oppervlakte,huisletter,pandstatus,postcode
    -> AttributeKeeper_2_Output
