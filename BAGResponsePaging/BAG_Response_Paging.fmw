FME workspace BAG_Response_Paging.fmw

Parameters:
- MaxFeatures = 15000   # Het maximum aantal features dat de WFS per request retourneert
- BaseURL = http://geodata.nationaalgeoregister.nl/bag/wfs?   # URL van de WFS-service
- FeatureType = bag:verblijfsobject   # FeatureType dat ingelezen moeten worden
- Filter = (bag:woonplaats='Groningen')   # CQL-filter voor het service request
- SRS = EPSG:28992   # Coördinatenstelsel waarin de service geometrie moet retourneren
- SortBy = bag:identificatie   # Attribuut waarop het resulaat van het service request gesorteerd moet worden
- Attributen = identificatie oppervlakte status gebruiksdoel openbare_ruimte huisnummer huisletter toevoeging postcode woonplaats actualiteitsdatum bouwjaar pandstatus pandidentificatie geometrie.Point.pos   # Attributen uit GML-respons die bewaard moeten blijven
- Node = bag:verblijfsobject   # " " Node in GML-output die attributen en geometrie bevat

AttributeKeeper_2_Output: Inspector

Bookmark: Het aantal features bepalen dat door de service geretourneerd wordt
Creator
    GEOMTYPE = Geometry Object
    NUM = 1
    CREATED -> HTTPCaller
HTTPCaller
    RESPONSE_HEADER_LIST_ATTR = _headers
    STATUS_CODE_ATTR = _http_status_code
    USE_COOKIES = No
    TRANSFER_TIMEOUT_LENGTH = 90
    CONNECTION_TIMEOUT_LENGTH = 60
    TARGET_ATTR = _response_body
    HTTP_METHOD = GET
    TARGET_URL = $(BaseURL)
    TARGET_ATTR_ENCODING = auto-detect
    SAVE_FILE = Attribute
    ADDITIONAL_URL_PARAMETERS = service;WFS version;2.0.0 request;GetFeature srs;$(SRS) typename;$(FeatureType) cql_filter;$(Filter) resulttype;hits
    FOLLOW_REDIRECTS = Yes
    VERIFY_SSL_CERTIFICATES = Yes
    ERROR_ATTR = _error
    -> XMLFlattener
    -> HTTPCaller_Output
XMLFlattener
    XML_SOURCE_TYPE = Attribute with XML document
    NEW_ATTRIBUTES = FeatureCollection.numberMatched
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    EMBEDDED_EXPRESSIONS = wfs:FeatureCollection
    -> AttributeKeeper
AttributeKeeper
    KEEP_ATTRS = FeatureCollection.numberMatched
    -> AttributeRenamer
AttributeRenamer
    ATTR_LIST = FeatureCollection.numberMatched,AantalFeatures,
    -> ExpressionEvaluator
HTTPCaller_Output: Inspector

Bookmark: Response paging
Note: Het aantal requests dat nodig is
ExpressionEvaluator
    VAL_ATTR = AantalRequests
    ACTION = Create New Attribute
    EXPRESSION = @ceil(@Evaluate(@Value(AantalFeatures)/$(MaxFeatures)))
    -> Cloner
Cloner
    COPIES = @Value(AantalRequests)
    COPYATT = StartIndex
    COPY -> ExpressionEvaluator_2
Note: De parameterwaarde StartIndex voor ieder request
ExpressionEvaluator_2
    ACTION = Overwrite Existing Attributes
    EXPRESSION = @Evaluate(@Value(StartIndex)*$(MaxFeatures))
    ATTRLIST = StartIndex
    -> HTTPCaller_2
Note: GetFeature requests
HTTPCaller_2
    RESPONSE_HEADER_LIST_ATTR = _headers
    STATUS_CODE_ATTR = _http_status_code
    USE_COOKIES = No
    TRANSFER_TIMEOUT_LENGTH = 90
    CONNECTION_TIMEOUT_LENGTH = 60
    TARGET_ATTR = _response_body
    HTTP_METHOD = GET
    TARGET_URL = $(BaseURL)
    TARGET_ATTR_ENCODING = auto-detect
    SAVE_FILE = Attribute
    ADDITIONAL_URL_PARAMETERS = service;wfs version;2.0.0 request;GetFeature typename;$(FeatureType) srs;$(SRS) cql_filter;$(Filter) startindex;@Value(StartIndex) count;$(MaxFeatures) sortby;$(SortBy) A
    FOLLOW_REDIRECTS = Yes
    VERIFY_SSL_CERTIFICATES = Yes
    ERROR_ATTR = _error
    -> XMLFragmenter

Bookmark: Respons van de WFS-service omzetten naar features
XMLFragmenter
    XML_SOURCE_TYPE = Attribute with XML document
    ATTRIBUTE_XML = _response_body
    EMBEDDED_EXPRESSIONS = $(Node)
    MERGE_ATTRS = No
    FRAGMENTS -> XMLFlattener_2
XMLFlattener_2
    XML_SOURCE_TYPE = Attribute with XML document
    NEW_ATTRIBUTES = $(Attributen)
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = xml_fragment
    EMBEDDED_EXPRESSIONS = $(Node)
    -> AttributeSplitter
AttributeSplitter
    LIST_NAME = pos
    ATTR_NAME = geometrie.Point.pos
    DROP_EMPTY_PARTS = No
    DELIMITER = " "
    TRIM_OPTION = Both
    -> VertexCreator
VertexCreator
    XVAL = @Value(pos{0})
    MODE_NAME = Add Point
    YVAL = @Value(pos{1})
    -> AttributeKeeper_2
AttributeKeeper_2
    KEEP_ATTRS = bouwjaar,identificatie,huisnummer,openbare_ruimte,pandidentificatie,actualiteitsdatum,gebruiksdoel,toevoeging,status,woonplaats,oppervlakte,huisletter,pandstatus,postcode
    -> AttributeKeeper_2_Output
