FME workspace bodemloket.fmw
Title: Bodemloket
Description: Workspace om de gegevens uit het Bodemloket in te lezen en weg te schrijven naar een shapefile. 
De workspace selecteert alleen gegevens binnen het interessegebied: heel Nederland of een provincie.
Het resultaat kan bestaan uit punten, lijnen en/of vlakken. Per geometrietype is er een aparte shapefile. 
De ArcGIS REST API van het Bodemloket retourneert maximaal 1.000 features per request. Dit is te weinig om alle gegevens binnen het interessegebied op te halen. Helaas ondersteunt de API geen response paging. Vandaar dat het interessegebied wordt opgedeeld in kleine vierkante deelgebieden, waarna per deelgebied een request wordt gedaan. 
Het is belangrijk om te controleren of er requests zijn die 1.000 features retourneren. In dat geval is de kans namelijk groot dat er in het deelgebied meer dan 1.000 features zijn en dat de verzameling features in de response onvolledig is. Maak in dat geval de afmetingen van het deelgebied kleiner.
History: 20-5-2019,Willy Tadema,

Parameters:
- provincie_filter = Zeeland
- tegelgrootte = 750   # Rijhoogte en kolombreedte grid (m)
- wfs_bestuurlijke_grenzen = https://geodata.nationaalgeoregister.nl/bestuurlijkegrenzen/wfs   # URL WFS Bestuurlijke Grenzen
- mapserver_bodemloket = https://www.gdngeoservices.nl/arcgis/rest/services/blk/lks_blk_rd/MapServer   # URL mapserver Bodemloket
- shape_folder = .\shape   # Output shape-folder
- geojson_folder = .\geojson   # Output GeoJSON-folder
- cql_filter:   # Python Script
      import fme
      
      filter = fme.macroValues.get("provincie_filter")
      
      if filter == "Alle provincies" or filter == "":
          return ""
      else:
          return "cql_filter=provincienaam='" + filter + "'"
- shape_naam:   # Python Script
      import fme
      
      filter = fme.macroValues.get("provincie_filter")
      
      if filter == "Alle provincies" or filter == "":
          return "Bodemloket_NL"
      else:
          return "Bodemloket_" + filter.replace("-", "_")
- feature_type:   # Python Script
      import fme
      
      filter = fme.macroValues.get("provincie_filter")
      
      if filter == "Alle provincies" or filter == "":
          return "landsgrens"
      else:
          return "provincies"

Readers:
- GEOJSON_1: GEOJSON from $(mapserver_bodemloket)/3/query?where=1%3D1&outFields=*&returnGeometry=true&f=geojson

Writers:
- ESRISHAPE_1: ESRISHAPE to $(shape_folder) in EPSG:4326

Note: GeoJSON is in EPSG:4326
Reprojector
    DEST = EPSG:4326
    INTERPOLATION_TYPE_NAME = Nearest Neighbor
    RASTER_CELL_SIZE = Preserve Cells
    RASTER_TOLERANCE = 0.0
    SOURCE = Read from feature
    REPROJECTED -> SpatialFilter_3 [Filter]
    REPROJECTED -> FeatureReader_3 [INITIATOR]

Bookmark: Begrenzing interessegebied bepalen
Creator
    GEOMTYPE = Geometry Object
    NUM = 1
    CREATED -> FeatureReader [INITIATOR]
FeatureReader
    ATTR_ACCUM_MODE = Only Use Result
    COMBINE_GEOM = Use Result
    DATASET = $(wfs_bestuurlijke_grenzen)?$(cql_filter)
    FEATURETYPES = $(feature_type)
    FORMAT = WFS
    INTERACT = <No Spatial Filter>
    OUTPUT_FEATURES_DISPLAY = Schema and Data Features
    WFS_CONNECTION_TIMEOUT = 90
    WFS_DISABLE_AUTOMATIC_READER_TYPE_SELECTION = NO
    WFS_DISABLE_XML_NAMESPACE_PROCESSING = NO
    WFS_ENFORCE_PATH_CONTINUITY_BY = SNAPPING_END_POINTS
    WFS_FLATTEN_XML_FRAGMENTS = NO
    WFS_IGNORE_APPLICATON_SCHEMA = no
    WFS_IGNORE_GETFEATURE_ERROR = No
    WFS_LOCAL_CACHE_EXPIRY = 60
    WFS_MAP_COMPLEX_PROPERTIES_AS = Nested Attributes
    WFS_MAP_EMBEDDED_OBJECTS_AS = ATTRIBUTES
    WFS_MAP_GEOMETRY_COLUMNS = YES
    WFS_MAP_PREDEFINED_GML_PROPERTIES = NO
    WFS_MAX_RESULT_FEATURES = 30000
    WFS_PREFERRED_VERSION = 1.1.0
    WFS_PREFER_DATASET_URL = No
    WFS_PREFER_POST = No
    WFS_TRANSFER_TIMEOUT = 90
    WFS_USE_OLD_READER = NO
    WFS_USE_SEARCH_ENVELOPE = NO
    WFS_XML_FRAGMENTS_AS_DOCUMENTS = YES
    <OTHER> -> Reprojector
    <OTHER> -> SpatialFilter [Filter]
    <OTHER> -> 2DGridAccumulator

Bookmark: Locaties (punten) in Bodemloket binnen het interessegebied opvragen
FeatureReader_3
    ATTRIBUTES = query,"id,WBB_DOSSIER_DBK,SIKB_ID,LOCATIECODE_BEVOEGD_GEZAG,BIS_LOCCODE,TYPE_CD,VERVOLG_WBB,STATUSVER,STATUS_OORD,ADMINISTRATOR_NM,NEN3610_ID_SOIL_LOCATION,NEN3610_ID_SOIL_MANAGEMENT,fme_geometry{0}"
    ATTR_ACCUM_MODE = Only Use Result
    COMBINE_GEOM = Use Result
    DATASET = $(mapserver_bodemloket)/0/query?where=1=1&outFields=*&f=geojson
    FORMAT = GEOJSON
    GEOJSON_FLATTEN_MODE = ALL_LEVELS
    GEOJSON_USE_BASENAME_AS_DEFAULT_FEATURE_TYPE = Yes
    GEOJSON_USE_SEARCH_ENVELOPE = NO
    INTERACT = Initiator Intersects Result
    OUTPUT_FEATURES_DISPLAY = Schema and Data Features
    query -> AttributeKeeper
    query -> FeatureMerger [REQUESTOR]

Bookmark: Grid maken voor interessegebied
2DGridAccumulator
    COL_ATTR = _column
    GRID_TYPE = Polygons
    ROW_ATTR = _row
    SIZE_TYPE = Cell Size
    STARTINGCORNER = Lower Left
    XINC = $(tegelgrootte)
    YINC = $(tegelgrootte)
    GRID -> SpatialFilter [Candidate]
SpatialFilter
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> BoundsExtractor
BoundsExtractor
    XMAX = xMax
    XMIN = xMin
    YMAX = yMax
    YMIN = yMin
    -> HTTPCaller

Bookmark: Locaties (vlakken) in Bodemloket binnen het interessegebied opvragen
Note: Locaties vlakken
HTTPCaller
    ADDITIONAL_URL_PARAMETERS = returnCountOnly;false where;1=1 outFields;* f;geojson geometryType;esriGeometryEnvelope inSR;28992 geometry;@Value(xMin),@Value(yMin),@Value(xMax),@Value(yMax) spatialRel;esriSpatialRelIntersects
    CONNECTION_TIMEOUT_LENGTH = 60
    ERROR_ATTR = _error
    FILE_PATH_ATTR = _response_file_path
    FOLLOW_REDIRECTS = Yes
    HTTP_METHOD = GET
    OUTPUT_FILENAME = $(geojson_folder)\@Value(xMin)_@Value(yMin).json
    RESPONSE_HEADER_LIST_ATTR = _headers
    SAVE_FILE = File
    SAVE_MULTI = No
    STATUS_CODE_ATTR = _http_status_code
    TARGET_URL = $(mapserver_bodemloket)/1/query
    TRANSFER_TIMEOUT_LENGTH = 90
    USE_COOKIES = No
    VERIFY_SSL_CERTIFICATES = No
    -> FeatureReader_2 [INITIATOR]
FeatureReader_2
    ATTR_ACCUM_MODE = Only Use Result
    COMBINE_GEOM = Use Result
    DATASET = @Value(_response_file_path)
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    <OTHER> -> SpatialFilter_3 [Candidate]
Note: Niet nodig als interressegebied heel NL is
SpatialFilter_3
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeExposer
AttributeExposer
    ATTR_LIST = ADMINISTRATOR_NM,BIS_LOCCODE,id,LOCATIECODE_BEVOEGD_GEZAG,NEN3610_ID_SOIL_LOCATION,NEN3610_ID_SOIL_MANAGEMENT,SIKB_ID,STATUS_OORD,STATUSVER,TYPE_CD,VERVOLG_WBB,WBB_DOSSIER_DBK,fme_feature_type
    -> DuplicateFilter
    -> StatisticsCalculator
DuplicateFilter
    INPUT_ORDERED_CHOICE = No
    KEYATTR = NEN3610_ID_SOIL_LOCATION SIKB_ID TYPE_CD BIS_LOCCODE id WBB_DOSSIER_DBK ADMINISTRATOR_NM LOCATIECODE_BEVOEGD_GEZAG VERVOLG_WBB NEN3610_ID_SOIL_MANAGEMENT STATUS_OORD STATUSVER
    UNIQUE -> FeatureMerger [REQUESTOR]
    UNIQUE -> CenterPointReplacer

Bookmark: Features verrijken met gegevens bevoegd gezag
CenterPointReplacer
    POINTTYPE = CENTER
    POINT -> AttributeKeeper
AttributeKeeper
    KEEP_ATTRS = fme_feature_type,id
    -> PointOnAreaOverlayer [POINT]
Note: Bevoegd gezag
query (reader GEOJSON_1)
    attributes: id int, AUTHORITY_DBK int, AUTHORITY_CD string, AUTHORITY_NM string, WEBSITE_BLN string, DOSSIER_BLN string, DISPLAY_CD string, WEBSITE_URL string, GEOMETRY.AREA int, GEOMETRY.LEN int
    -> PointOnAreaOverlayer [AREA]
PointOnAreaOverlayer
    ATTR_ACCUM_MODE = Merge Incoming
    ATTR_CONFLICT_RES = Use Original
    DEAGGREGATE_INPUT = Yes
    OV_ATTR = _overlaps
    POLYS_FIRST = NO
    POINT -> FeatureMerger [SUPPLIER]
FeatureMerger
    ATTR_ACCUM_MODE = Merge Supplier
    ATTR_CONFLICT_RES = Use Requestor
    IGNORE_NULLS = No
    JOIN_KEYS = @Value(id) @Value(id) AUTO
    MERGE_TYPE = Attributes Only
    PROCESS_DUPS = NO
    REJECT_NULL_MISSING_KEYS = No
    SUPPLIERS_FIRST = No
    MERGED -> AttributeManager

Bookmark: Checken of er minder dan 1.000 features per request zijn
StatisticsCalculator
    COMPUTE_HISTOGRAM = NO
    COUNT_ATTR = _count
    GROUP_BY = fme_feature_type
    PREPEND_ATTR_NAME_CHOICE = For multiple results only
    STATS_ATTRS = fme_feature_type
    SUMMARY -> Sorter
Sorter
    SORT_PARM = _count NUMERIC DESCENDING
    SORTED -> Tester
Tester
    BOOL_OP = OR
    COMPOSITE_TEST = 1
    TEST_CLAUSE = TEST @Value(_count) = 1000
    TEST_MODE = TEST
    PASSED -> Logger
Logger
    LOG_FEATURE = LOG_ONLY
    MAXCOORDS = 20
    MAXFEATS = 20
    MESSAGE = @Value(fme_feature_type).json bevat 1.000 features. Dit is het maximum aantal features dat de map server per request retourneert. Wellicht ontbreken er dus features in het GeoJSON bestand!
    SEVERITY = WARN

Bookmark: Resultaat wegschrijven
Note: Afgeleide attributen aanmaken
AttributeManager
    ATTR_TABLE:
      SET_TO geometrietype = FME_CONDITIONAL:DEFAULT_VALUE'vlakken'BOOL_OP;OR;COMPOSITE_TEST;1;TEST @Value(fme_feature_type) = query'punten'FME_NUM_CONDITIONS2___
      RENAME_SET_VALUE id > ID
      REMOVE GEOMETRY.AREA
      REMOVE GEOMETRY.LEN
      REMOVE _predicate
      REMOVE _overlaps
      SET_TO rapportVoortgangBodemonderzoek = FME_CONDITIONAL:DEFAULT_VALUE'_FME_NO_OP_'BOOL_OP;OR;COMPOSITE_TEST;1;TEST @Value(DOSSIER_BLN) = J'https://www.bodemloket.nl/bodemloket/tools/report/guid/@Value(NEN3610_ID_SOIL_MANAGEMENT)/@Value(LOCATIECODE_BEVOEGD_GEZAG)/SIKB_12'FME_NUM_CONDITIONS2___
      SET_TO voortgangBodemonderzoek = FME_CONDITIONAL:DEFAULT_VALUE'Gegevens aanwezig, status onbekend'BOOL_OP;OR;COMPOSITE_TEST;1;TEST @Value(TYPE_CD) IN 4,5,6,7,8,15,16,17,18'Saneringsactiviteit'BOOL_OP;OR;COMPOSITE_TEST;1;TEST @Value(TYPE_CD) IN 9,10,11,12,20,21'Voldoende onderzocht/gesaneerd'BOOL_OP;OR;COMPOSITE_TEST;1;TEST @Value(TYPE_CD) IN 1,2,3,13,14 'Onderzoek uitvoeren'BOOL_OP;OR;COMPOSITE_TEST;1;TEST @Value(TYPE_CD) IN 19,22'Historie bekend'FME_NUM_CONDITIONS5___
    -> GeometryFilter
GeometryFilter
    BREAK_AGG = No
    GEOM_PORT_NAMES = Point Line Area
    POINT -> Groningen0000 (writer ESRISHAPE_1)
    LINE -> Groningen00 (writer ESRISHAPE_1)
    AREA -> Groningen (writer ESRISHAPE_1)
Groningen0000 (writer ESRISHAPE_1)
    attributes: geometriet char(200), ADMINISTRA char(200), BIS_LOCCOD char(200), ID char(200), LOCATIECOD char(200), NEN3610_ID char(200), NEN3610_00 char(200), SIKB_ID char(200), STATUS_OOR char(200), STATUSVER char(200), TYPE_CD char(200), VERVOLG_WB char(200), WBB_DOSSIE char(200), AUTHORITY_ number(20,0), AUTHORIT00 char(254), AUTHORIT01 char(254), WEBSITE_BL char(254), DOSSIER_BL char(254), DISPLAY_CD char(254), WEBSITE_UR char(254), rapportVoo char(200), voortgangB char(200), fme_geomet char(200)
Groningen00 (writer ESRISHAPE_1)
    attributes: geometriet char(200), ADMINISTRA char(200), BIS_LOCCOD char(200), ID char(200), LOCATIECOD char(200), NEN3610_ID char(200), NEN3610_00 char(200), SIKB_ID char(200), STATUS_OOR char(200), STATUSVER char(200), TYPE_CD char(200), VERVOLG_WB char(200), WBB_DOSSIE char(200), AUTHORITY_ number(20,0), AUTHORIT00 char(254), AUTHORIT01 char(254), WEBSITE_BL char(254), DOSSIER_BL char(254), DISPLAY_CD char(254), WEBSITE_UR char(254), rapportVoo char(200), voortgangB char(200), fme_geomet char(200)
Groningen (writer ESRISHAPE_1)
    attributes: geometriet char(200), ADMINISTRA char(200), BIS_LOCCOD char(200), ID char(200), LOCATIECOD char(200), NEN3610_ID char(200), NEN3610_00 char(200), SIKB_ID char(200), STATUS_OOR char(200), STATUSVER char(200), TYPE_CD char(200), VERVOLG_WB char(200), WBB_DOSSIE char(200), AUTHORITY_ number(20,0), AUTHORIT00 char(254), AUTHORIT01 char(254), WEBSITE_BL char(254), DOSSIER_BL char(254), DISPLAY_CD char(254), WEBSITE_UR char(254), rapportVoo char(200), voortgangB char(200), fme_geomet char(200)
