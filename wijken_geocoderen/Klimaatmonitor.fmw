FME workspace Klimaatmonitor.fmw

Parameters:
- SourceDataset_XLSXR = $(FME_MF_DIR_USERTYPED)\Energiegebruik 2017 - Wijken 2017 van Zuid-Holland.xls   # Source Microsoft Excel File(s)

Readers:
- XLSXR_1: XLSXR from $(SourceDataset_XLSXR)

Note: Download bronbestand via deze link: / https://klimaatmonitor.databank.nl/Jive?workspace_guid=9ebf4cf6-0536-4cb0-bed7-8516c15e86a7
Energiegebruik 2017 Wijken 2017 (reader XLSXR_1)
    attributes: A char(66), B char(1), C char(1), D char(10), E char(9), F char(9)
    -> HTTPCaller
Energiegebruik_wijken_in_Z-H_2017: Inspector

Bookmark: Wijknaam, -code en -geometrie ophalen bij LocatieServer
HTTPCaller
    ADDITIONAL_URL_PARAMETERS = q;wijknaam:@ReplaceString(@Value(A) ,Zuid-Holland:, ) fq;type:wijk AND provincienaam:"Zuid-Holland" rows;1 fl;wijknaam, wijkcode, geometrie_rd
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://geodata.nationaalgeoregister.nl/locatieserver/v3/free
    TRANSFER_TIMEOUT_LENGTH = 90
    USE_COOKIES = No
    VERIFY_SSL_CERTIFICATES = No
    -> JSONExtractor
JSONExtractor
    EXTRACT_QUERY_TABLE = wijknaam json["response"]["docs"][*]["wijknaam"] wijkcode json["response"]["docs"][*]["wijkcode"] geometrie_rd json["response"]["docs"][*]["geometrie_rd"]
    JSON_DOCUMENT = @Value(_response_body)
    READ_FROM_FILE = NO
    EVALUATED -> GeometryReplacer

Bookmark: Geometrie aanmaken
GeometryReplacer
    KIND_LONG = OGC Well Known Text
    OGC_WKT_PRECISION_DISPLAY = 64-bit
    REMOVE_ATTRIBUTE = Yes
    SOURCE = @Value(geometrie_rd)
    -> CoordinateSystemSetter
CoordinateSystemSetter
    COORDSYS = EPSG:28992
    -> StringReplacer

Bookmark: Uitvoer opschonen
StringReplacer
    CASE = NO
    FIND_TEXT = ?
    NO_MATCH = _FME_NO_OP_
    REGEXP = NO
    SRC_ATTRS = E,D,B,C,F
    -> AttributeManager
AttributeManager
    ATTR_TABLE:
      REMOVE A
      RENAME_SET_VALUE B > Totaal elektriciteitsgebruik bedrijven en instellingen op grondgebied (kWh)
      RENAME_SET_VALUE C > Totaal gasgebruik bedrijven en instellingen excl. gasgebruik energieproductie op grondgebied (m3)
      RENAME_SET_VALUE D > Elektriciteitsgebruik woningen (kWh)
      RENAME_SET_VALUE E > Gasgebruik woningen (m3)
      RENAME_SET_VALUE F > Gasgebruik woningen temperatuurgecorrigeerd (m3)
      REMOVE _response_body
      REMOVE _http_status_code
    -> Energiegebruik_wijken_in_Z-H_2017
