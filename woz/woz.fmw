FME workspace woz.fmw
Title: WOZ-waarde opvragen
Description: Deze workspace demonstreert hoe je met LocatieServer en de API van het WOZ-waardeloket de WOZ-waarde van een woning kan opvragen. 
Input is een adres. Dat kan een straatnaam+huisnummeraanduiding+woonplaats zijn, maar ook een postcode+huisnummeraanduiding, of een BAG-identificatienummer.
Soms wordt er geen WOZ-waarde gevonden. Mogelijke oorzaken:
    Alleen WOZ-waarden van woningen zijn openbaar. Als het pand in de BAG (nog) een ander gebruikersdoel heeft dan 'woonfunctie', wordt de WOZ-waarde niet gedeeld via de WOZ-waardeloket API. 
    Voor de betreffende woning is nog geen WOZ-waarde beschikbaar.
Let op: volgens de gebruiksvoorwaarden van het WOZ-waardeloket mag je niet geautomatiseerd via de API gegevens ophalen!
Tekst op de website:
    Het massaal (geautomatiseerd) onttrekken van gegevens aan het loket voor openbare WOZ-waarden van woningen is niet toegestaan. Het loket is op basis van artikel 40a, eerste lid, van de Wet WOZ uitsluitend bedoeld voor het individueel raadplegen van afzonderlijke woningen. Ook het op geautomatiseerde wijze ontlenen van gegevens aan dit loket en deze informatie verstrekken aan derden is niet toegestaan. Voor het massaal en/of geautomatiseerd opvragen van WOZ-waarden van woningen zijn nog geen nadere regels gesteld als bedoeld in artikel 40a, tweede lid, van de Wet WOZ. Bij ontbreken van deze nadere regelgeving is deze vorm van opvragen van WOZ-waarden uit het loket niet toegestaan.

Note: Testdataset maken
PythonCreator
    NEW_ATTRIBUTES = query
    PYTHONSOURCE_NEW:
      import fmeobjects

      class FeatureCreator(object):
          def __init__(self):
              pass

          def input(self,feature):
              lijst = ["Schoolstraat 1 Groningen", "9712 JP 1", "0014010011034119", "Sint Jansstraat 4 Groningen"]

              for item in lijst:
                  feature = fmeobjects.FMEFeature()
                  feature.setAttribute("query", item)
                  self.pyoutput(feature)

          def close(self):
              pass
    PYTHONSYMBOL = FeatureCreator
    -> WOZQuerier
WOZQuerier
    QUERY = @Value(query)
    -> WOZQuerier_Output
WOZQuerier_Output: Inspector

FME custom transformer WOZQuerier
De input van deze transformer is een adres (vrij veld). Het hoeft geen volledig adres te zijn, postcode + huisnummer is al voldoende.
Op basis van het adres wordt met behulp van PDOK LocatieServer het BAG-identificatienummer opgevraagd.
Met het BAG-identificatienummer kan vervolgens de WOZ-waarde opgevraagd worden bij het WOZ-waardeloket (www.wozwaardeloket.nl).
In de response van het WOZ-waardeloket, krijg je ook historie terug. Die negeren we. We zijn alleen geïnteresseerd in de actuele WOZ-waarde.
Voor sommige BAG-identificatienummers bevat het WOZ-waardeloket geen WOZ-waarde. Het veld huidige_woz_waarde blijft dan leeg.

Parameters:
- QUERY = @Value(query)   # query

Input (input)
    -> HTTPCaller
Note: BAG-Identificatienummer ophalen via LocatieServer
HTTPCaller
    ADDITIONAL_URL_PARAMETERS = q;@Value(query) fl;weergavenaam, adresseerbaarobject_id fq;type:adres rows;1
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://geodata.nationaalgeoregister.nl/locatieserver/v3/free
    TRANSFER_TIMEOUT_LENGTH = 90
    USE_COOKIES = No
    VERIFY_SSL_CERTIFICATES = No
    -> JSONExtractor
JSONExtractor
    EXTRACT_QUERY_TABLE = adresseerbaarobject_id json["response"]["docs"][*]["adresseerbaarobject_id"] adres json["response"]["docs"][*]["weergavenaam"]
    JSON_DOCUMENT = @Value(_response_body)
    READ_FROM_FILE = NO
    EVALUATED -> HTTPCaller_2
Note: Cookie ophalen
HTTPCaller_2
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://www.wozwaardeloket.nl
    TRANSFER_TIMEOUT_LENGTH = 90
    USE_COOKIES = Yes
    VERIFY_SSL_CERTIFICATES = No
    -> HTTPCaller_3
Note: WOZ-waarde opvragen
HTTPCaller_3
    CONNECTION_TIMEOUT_LENGTH = 60
    ERROR_ATTR = _error
    FOLLOW_REDIRECTS = Yes
    HTTP_METHOD = POST
    SAVE_FILE = Attribute
    STATUS_CODE_ATTR = _http_status_code
    TARGET_ATTR = _response_body
    TARGET_ATTR_ENCODING = auto-detect
    TARGET_URL = https://www.wozwaardeloket.nl/woz-proxy/wozloket
    TRANSFER_TIMEOUT_LENGTH = 90
    UPLOAD_BODY:
      <wfs:GetFeature xmlns:wfs="http://www.opengis.net/wfs" service="WFS" version="1.1.0" xsi:schemaLocation="http://www.opengis.net/wfs http://schemas.opengis.net/wfs/1.1.0/wfs.xsd" xmlns:xsi="http://www.w3.org/2001/XMLSchema-instance"><wfs:Query typeName="wozloket:woz_woz_object" srsName="EPSG:28992" xmlns:WozViewer="http://WozViewer.geonovum.nl" xmlns:ogc="http://www.opengis.net/ogc">
      <ogc:Filter xmlns:ogc="http://www.opengis.net/ogc"><ogc:PropertyIsEqualTo matchCase="true"><ogc:PropertyName>wobj_bag_obj_id</ogc:PropertyName><ogc:Literal>@Evaluate(@Value(adresseerbaarobject_id))</ogc:Literal></ogc:PropertyIsEqualTo>
      </ogc:Filter></wfs:Query></wfs:GetFeature>
    UPLOAD_CONTENT_TYPE = XML (application/xml)
    UPLOAD_TYPE = Specify Upload Body
    USE_COOKIES = Yes
    VERIFY_SSL_CERTIFICATES = No
    -> JSONExtractor_2
JSONExtractor_2
    EXTRACT_QUERY_TABLE = huidige_woz_waarde json["features"][1]["properties"]["wobj_huidige_woz_waarde"]
    JSON_DOCUMENT = @Value(_response_body)
    READ_FROM_FILE = NO
    EVALUATED -> AttributeKeeper
AttributeKeeper
    KEEP_ATTRS = adresseerbaarobject_id,adres,huidige_woz_waarde,query
    -> Output (output)
Output (output)
