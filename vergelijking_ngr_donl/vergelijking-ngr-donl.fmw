FME workspace vergelijking-ngr-donl.fmw

Parameters:
- DestDataset_XLSXW = Verschillen NGR en DONL.xlsx   # Destination Microsoft Excel File

Writers:
- XLSXW_1: XLSXW to $(DestDataset_XLSXW)

Note: Provincies: / - naam / - organisatienaam in NGR / - organisatienaam op data.overheid.nl
PythonCreator
    NEW_ATTRIBUTES = provincie organisatie_ngr organisatie_donl
    PYTHONSOURCE_NEW:
      import fmeobjects

      class FeatureCreator(object):
          def __init__(self):
              pass

          def input(self,feature):
              provincies = [["Drenthe", "Provincie Drenthe", "Drenthe"],    # label, organisatie in NGR, organisatie in data.overheid.nl
                            ["Flevoland", "Provincie Flevoland", "Flevoland"],
                            ["Fryslân", "Provincie Fryslân", "Fryslan"],
                            ["Gelderland", "Provincie Gelderland", "Gelderland"],
                            ["Groningen", "Provincie Groningen", "Groningen_(provincie)"],
                            ["Limburg", "Provincie Limburg", "Limburg"],
                            ["Noord-Brabant", "Provincie Noord-Brabant", "Noord-Brabant"],
                            ["Noord-Holland", "Provincie Noord-Holland", "Noord-Holland"],
                            ["Overijssel", "Provincie Overijssel", "Overijssel"],
                            ["Utrecht", "Provincie Utrecht", "Utrecht_(provincie)"],
                            ["Zeeland", "Provincie Zeeland", "Zeeland_(provincie)"],
                            ["Zuid-Holland", "Provincie Zuid-Holland", "Zuid-Holland"]]
              for provincie in provincies:
                  feature = fmeobjects.FMEFeature()
                  feature.setAttribute("provincie", provincie[0])
                  feature.setAttribute("organisatie_ngr", provincie[1])
                  feature.setAttribute("organisatie_donl", provincie[2])
                  self.pyoutput(feature)

          def close(self):
              pass
    PYTHONSYMBOL = FeatureCreator
    -> Tester_2
Tester_2
    BOOL_OP = OR
    COMPOSITE_TEST = 1
    TEST_CLAUSE = TEST @Value(provincie) = Zuid-Holland
    TEST_MODE = TEST
    PASSED -> NGRCaller
    PASSED -> DONLCaller
Note: Lijst van alle datasets in het Nationaal Georegister per provincie
Note: Let op: als een provincie méér dan 1.000 datasets in het NGR heeft, gaat het mis! / Drenthe hangt hier tegenaan! / Oplossing is om het script uit te breiden met paging.
NGRCaller
    NGR_base_URL = https://nationaalgeoregister.nl/geonetwork/srv/dut/q
    organisatie = @Value(organisatie_ngr)
    -> FeatureMerger [REQUESTOR]
DONLCaller: DONLcaller
    DONL_base_URL = https://data.overheid.nl/data
    organisatie = @Value(organisatie_donl)
    -> FeatureMerger [SUPPLIER]
FeatureMerger
    ATTR_ACCUM_MODE = Merge Supplier
    ATTR_CONFLICT_RES = Use Requestor
    IGNORE_NULLS = No
    JOIN_KEYS = @Value(uuid) @Value(uuid) AUTO
    MERGE_TYPE = Attributes Only
    PROCESS_DUPS = NO
    REJECT_NULL_MISSING_KEYS = No
    SUPPLIERS_FIRST = No
    UNMERGED_REQUESTOR -> AttributeCreator
    UNUSED_SUPPLIER -> Niet in NGR, wel in DONL (writer XLSXW_1)
Note: Licentie aanwezig?
AttributeCreator
    ATTR_TABLE = SET_TO licentieAanwezig = FME_CONDITIONAL:DEFAULT_VALUE'0'BOOL_OP;OR;COMPOSITE_TEST;<Unused>;TEST licenseLink ATTRIBUTE_HAS_A_VALUE _FME_BLANK_STRING_'1'FME_NUM_CONDITIONS2___
    -> AttributeCreator_2
Note: Distributie aanwezig?
AttributeCreator_2
    ATTR_TABLE = SET_TO distributieAanwezig = FME_CONDITIONAL:DEFAULT_VALUE'0'BOOL_OP;OR;COMPOSITE_TEST;<Unused>;TEST link ATTRIBUTE_HAS_A_VALUE _FME_BLANK_STRING_'1'FME_NUM_CONDITIONS2___
    -> AttributeCreator_3
Note: Onderwerp aanwezig?
AttributeCreator_3
    ATTR_TABLE = SET_TO onderwerpAanwezig = FME_CONDITIONAL:DEFAULT_VALUE'0'BOOL_OP;OR;COMPOSITE_TEST;<Unused>;TEST topicCat ATTRIBUTE_HAS_A_VALUE _FME_BLANK_STRING_'1'FME_NUM_CONDITIONS2___
    -> Wel in NGR, niet in DONL (writer XLSXW_1)
Wel in NGR, niet in DONL (writer XLSXW_1)
    attributes: provincie auto(20), uuid auto(20), title auto(20), licenseLink auto(20), link auto(20), format auto(20), licentieAanwezig boolean(20), distributieAanwezig boolean(20), contactpuntAanwezig boolean(20), onderwerpAanwezig boolean(20)
Niet in NGR, wel in DONL (writer XLSXW_1)
    attributes: provincie auto(20), uuid auto(20), id auto(20), title auto(20), license_id auto(20)

FME custom transformer DONLcaller

Parameters:
- organisatie =   # Organisatie
- DONL_base_URL = https://data.overheid.nl/data   # https Base URL data.overheid.nl CKAN api

Input (input)
    -> HTTPCaller_2
HTTPCaller_2
    ADDITIONAL_URL_PARAMETERS = q;+publisher:"http://standaarden.overheid.nl/owms/terms/$(organisatie)" +source_catalog:"https://nationaalgeoregister.nl" rows;1000 start;0 sort;metadata_created asc
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = json
    TARGET_ATTR_ENCODING = auto-detect
    TARGET_URL = $(DONL_base_URL)/api/3/action/package_search
    TRANSFER_TIMEOUT_LENGTH = 90
    UPLOAD_CONTENT_TYPE = Text (text/plain)
    UPLOAD_TYPE = Specify Upload Body
    USE_COOKIES = No
    VERIFY_SSL_CERTIFICATES = No
    -> JSONFragmenter_2
JSONFragmenter_2
    EXPLODE_FORMAT = JSON
    EXTRACT_ATTR = No
    JSON_ATTR = json
    JSON_QUERY = json["result"]["results"][*]
    READ_FROM_FILE = NO
    REJECT_EMPTY_LISTS = YES
    FRAGMENTS -> JSONExtractor
JSONExtractor
    EXTRACT_QUERY_TABLE = id json["id"] identifier json["identifier"] title json["title"] license_id json["license_id"] resources json["resources"]
    JSON_DOCUMENT = @Value(json)
    READ_FROM_FILE = NO
    EVALUATED -> AttributeCreator_3
AttributeCreator_3
    ATTR_TABLE = SET_TO uuid = @Substring(@Value(identifier),48,@Evaluate(@StringLength(@Value(identifier))-48))
    -> Output (output)
Output (output)

FME custom transformer NGRCaller

Parameters:
- organisatie =   # Organisatie
- NGR_base_URL = https://nationaalgeoregister.nl/geonetwork/srv/dut/q   # https Base URL NGR api

Input (input)
    -> HTTPCaller
HTTPCaller
    ADDITIONAL_URL_PARAMETERS = _content_type;json bucket;s101 facet.q; fast;index from;1 to;1000 isChild;'false' orgName;$(organisatie) resultType;details sortBy;relevance
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = $(NGR_base_URL)
    TRANSFER_TIMEOUT_LENGTH = 90
    USE_COOKIES = No
    VERIFY_SSL_CERTIFICATES = Yes
    -> JSONFragmenter
JSONFragmenter
    EXPLODE_FORMAT = JSON
    EXTRACT_ATTR = No
    JSON_ATTR = _response_body
    JSON_QUERY = json["metadata"][*]
    READ_FROM_FILE = NO
    REJECT_EMPTY_LISTS = YES
    FRAGMENTS -> JSONExtractor
JSONExtractor
    EXTRACT_QUERY_TABLE = uuid json["geonet:info"]["uuid"] title json["title"] licenseLink json["licenseLink"] responsibleParty json["responsibleParty"] format json["format"] link json["link"] topicCat json["topicCat"]
    JSON_DOCUMENT = @Value(_response_body)
    READ_FROM_FILE = NO
    EVALUATED -> AttributeRenamer
AttributeRenamer
    ATTR_TABLE = RENAME_SET_DEFAULT geonet:info.uuid > uuid
    -> AttributeManager
AttributeManager
    ATTR_TABLE:
      REMOVE _headers{}.name
      REMOVE _headers{}.value
      REMOVE _response_body
      REMOVE _http_status_code
      REMOVE json_type
      REMOVE json_index
      SET_TO contactpuntAanwezig = @Evaluate(@FindString(@Value(responsibleParty),contactpunt) != -1)
    -> Output (output)
Output (output)
