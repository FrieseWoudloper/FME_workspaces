FME workspace TOP25raster.fmw

Parameters:
- SourceDataset_OGCKML = https://www.pdok.nl/sites/default/files/kaart_data/topraster_025k.kml   # URL van het KML-bestand met de kaartbladindeling
- SourceDataset_SHAPE = ..\Brondata\uitsnede.shp   # Bestandspad van het shape-bestand met de uitsnede voor Frsl./Gr./Dr.
- DestDataset_GEOTIFF = ..\Output   # Map waar de GeoTIFF-bestanden worden opgeslagen
- DestDataset_SHAPE = ..\Output   # Map waar het shape-bestand met de kaartbladindeling wordt opgeslagen
- DestDataset_AUTOCAD_OD = ..\Output\Indeling.dwg   # Map waar het DWG-bestand met de kaartbladindeling wordt opgeslagen

Readers:
- OGCKML_1: OGCKML from $(SourceDataset_OGCKML)
- SHAPE_1: SHAPE from $(SourceDataset_SHAPE)

Writers:
- GEOTIFF_1: GEOTIFF to $(DestDataset_GEOTIFF)
- SHAPE_2: SHAPE to $(DestDataset_SHAPE) in EPSG:28992
- AUTOCAD_OD_1: AUTOCAD_OD to $(DestDataset_AUTOCAD_OD)

Note: Datum: 07-03-2016 / Versie: 1.0 / Auteur: Willy Bakker / Omschrijving: Workspace voor het downloaden van TOP25raster kaartbladen en het maken van een shape- en DWG-bestand met de kaartbladindeling / Published parameters: / SourceDataset_OGCKML URL van het KML-bestand met de kaartbladindeling / SourceDataset_SHAPE Bestandspad van het shape-bestand met de uitsnede voor Frsl./Gr./Dr. / DestDataset_GEOTIFF Map waar de GeoTIFF-bestanden worden opgeslagen / DestDataset_SHAPE Map waar het shape-bestand met de kaartbladindeling wordt opgeslagen / DestDataset_AUTOCAD_OD Map waar het DWG-bestand met de kaartbladindeling wordt opgeslagen
Note: KML met allle kaartbladen van de TOP25raster
Placemark (reader OGCKML_1)
    -> HTMLToXHTMLConverter
Note: Beschijving in HTML omzetten naar XML
HTMLToXHTMLConverter
    IGNORE_WARNINGS = yes
    HTML_INPUT_TYPE = Attribute Specifying HTML Text
    XHTML_OUTPUT_TYPE = Attribute to Contain XHTML Text
    XHTML_OUTPUT_ATTR = kml_description
    OUTPUT_ENCODING_PROMPT = Unicode 8-bit (utf-8)
    HTML_ATTR_TEXT = kml_description
    LIST_NAME = _html_error
    INPUT_ENCODING = utf-8
    PASSED -> XMLFlattener
Note: XML elementen omzetten naar feature attributen
XMLFlattener
    EMBEDDED_EXPRESSIONS = tr
    NEW_ATTRIBUTES = td{1}.a.href
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = kml_description
    XML_SOURCE_TYPE = Attribute with XML document
    -> AttributeRenamer
    -> XMLFlattener_Output
XMLFlattener_Output: Inspector
Note: Attributen hernoemen naar kaartbladnr en hyperlink
AttributeRenamer
    ATTR_LIST = kml_name,kaartblad,,td{1}.a.href,hyperlink,
    -> AttributeRemover
Note: Overbodige attributen verwijderen
Note: Het duurt 7 minuten om de workspace uit te voeren.
AttributeRemover
    REMOVE_ATTRS = _html_error,kml_description
    -> Reprojector
Note: Herprojecteren naar EPSG:28992
Reprojector
    SOURCE = Read from feature
    RASTER_CELL_SIZE = Preserve Cells
    INTERPOLATION_TYPE_NAME = Nearest Neighbor
    DEST = EPSG:28992
    REPROJECTED -> Clipper [input 2]
Note: Shape-bestand met uitsnede van het gebied / waarvoor we de TOP25raster willen downloaden
uitsnede (reader SHAPE_1)
    attributes: provincien char(254)
    -> Clipper [input 1]
Note: Kaartbladen binnen interessegebied selecteren
Clipper
    CLIP_TYPE = Multiple Clippers
    BOUNDARY_CASES = Treat as Inside
    CREATE_AGGREGATES = No
    PRESERVE_CLIPPEE_EXTENTS = No
    CLIPPED_ATTR = _clipped
    INSIDE -> FeatureReader
Note: ZIP-bestanden downloaden en / TIF-bestanden inlezen
FeatureReader
    GEOTIFF_READ_OFFSETS_IN_CS_UNITS = No
    GEOTIFF_PREFER_FILE_CS_UNITS = Yes
    GEOTIFF_USE_SEARCH_ENVELOPE = NO
    GEOTIFF_IGNORE_RASTER_TYPE_KEY = No
    GEOTIFF_FEATURE_TYPE_NAME = FORMAT_NAME
    COMBINE_GEOM = Use Result
    ATTR_CONFLICT_RES = Use Result
    ATTR_ACCUM_MODE = Merge Initiator and Result
    GEOTIFF_CLIP_TO_ENVELOPE = NO
    FORMAT = GEOTIFF
    FEATURETYPES_RADIO = FEATURETYPES
    DATASET = @Value(hyperlink)
    INTERACT = <No Spatial Filter>
    GEOTIFF_APPLY_GCPS = No
    <OTHER> -> AttributeExposer
Note: Attribuut fme_basename
AttributeExposer
    ATTR_LIST = fme_basename
    -> AttributeCreator
Note: Attributen bestandsnaam en revisiejaar aanmaken
AttributeCreator
    ATTR_LIST = revisie,@Substring(@Value(fme_basename), @Evaluate(@FindString(@Value(fme_basename),-top25raster-) + 13), @StringLength(@Value(fme_basename))),bestand,@Value(fme_basename).tif
    -> test (writer GEOTIFF_1)
    -> BoundingBoxReplacer
Note: TIF-bestanden wegschrijven / inclusief world-files
test (writer GEOTIFF_1)
Note: Boundingbox van kaartbladen bepalen
BoundingBoxReplacer
    BOXTYPE = Bounding Box
    BOX -> Indeling (writer SHAPE_2)
    BOX -> Indeling (writer AUTOCAD_OD_1)
    BOX -> LabelPointReplacer
Note: Shape-bestand
Indeling (writer SHAPE_2)
    attributes: kaartblad char(200), bestand char(200), revisie char(200)
LabelPointReplacer
    HEIGHT = 2500
    LABATTR = @Value(kaartblad)
    ALWAYSROTATE = yes
    LabelPoint -> DWGStyler
DWGStyler
    TEXT_TYPE = Multi-Text
    TEXT_JUSTIFICATION = Middle Center
    TEXT_FONT = MS Shell Dlg 2,12
    DWGStyled -> Tekst (writer AUTOCAD_OD_1)

Bookmark: AutoCAD-bestand
Indeling (writer AUTOCAD_OD_1)
    attributes: kaartblad char(200), bestand char(200), revisie char(200)
Tekst (writer AUTOCAD_OD_1)
    attributes: kaartblad char(200)
