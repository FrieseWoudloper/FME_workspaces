FME workspace voorbeeld_cbs.fmw
Title: Voorbeeld CBS
Description: Het doel van deze workspace is om te demonstreren hoe je:
* een dataset van het CBS kunt inlezen met behulp van de WFS,
* een dataset van het CBS kunt inlezen via de OData Feed,
* de combinatie van deze twee datasets kunt filteren op de provinciegrens.
History: 19-11-2018,Willy Tadema,

Parameters:
- SourceDataset_OData = https://opendata.cbs.nl/ODataFeed/odata/84314NED/TypedDataSet   # Source OData URL

Note: OData reader werkt in dit geval niet, vandaar de workaround. / Zie https://knowledge.safe.com/questions/59276/importing-odata-feed-with-https-url.html
Note: Inlezen van CBS-dataset 84314NED (Energieverbruik particuliere woningen 2017)
AttributeValueMapper_Output: Inspector

Bookmark: Aantal requests dat nodig is om de hele dataset op te vragen
Creator
    GEOMTYPE = Geometry Object
    NUM = 1
    CREATED -> HTTPCaller
HTTPCaller
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = count
    TARGET_ATTR_ENCODING = auto-detect
    TARGET_URL = $(SourceDataset_OData)/$count
    TRANSFER_TIMEOUT_LENGTH = 90
    USE_COOKIES = No
    VERIFY_SSL_CERTIFICATES = No
    -> Cloner
Cloner
    COPIES = @ceil(@Evaluate(@Value(count) / 10000))
    COPYATT = number
    COPY -> AttributeCreator

Bookmark: Datasets inlezen
AttributeCreator
    ATTR_TABLE = SET_TO request = FME_CONDITIONAL:DEFAULT_VALUE'$(SourceDataset_OData)?$format=json&$skip=@Evaluate(@Value(number)*10000)'BOOL_OP;OR;COMPOSITE_TEST;<Unused>;TEST @Value(number) = 0'$(SourceDataset_OData)?$format=json'FME_NUM_CONDITIONS2___
    -> HTTPCaller_2
HTTPCaller_2
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = @Value(request)
    TRANSFER_TIMEOUT_LENGTH = 90
    USE_COOKIES = No
    VERIFY_SSL_CERTIFICATES = No
    -> JSONFragmenter
JSONFragmenter
    EXPLODE_FORMAT = JSON
    EXTRACT_ATTR = Yes
    JSON_ATTR = _response_body
    JSON_QUERY = json["value"][*]
    NEW_ATTRIBUTES = ID Woningkenmerken WijkenEnBuurten Gemeentenaam_1 SoortRegio_2 Codering_3 GemiddeldAardgasverbruik_4 GemiddeldElektriciteitsverbruik_5 Stadsverwarming_6 IndelingswijzigingWijkenEnBuurten_7
    RECURSIVE = Yes
    FRAGMENTS -> AttributeManager
AttributeManager
    ATTR_TABLE:
      REMOVE request
      REMOVE _creation_instance
      REMOVE _headers{}.name
      REMOVE _headers{}.value
      REMOVE count
      REMOVE _http_status_code
      REMOVE number
      REMOVE _response_body
      REMOVE json_type
      REMOVE json_index
      RENAME_SET_VALUE Gemeentenaam_1 > Gemeentenaam
      RENAME_SET_VALUE SoortRegio_2 > SoortRegio
      RENAME_SET_VALUE Codering_3 > Codering
      RENAME_SET_VALUE GemiddeldAardgasverbruik_4 > GemiddeldAardgasverbruik_m3
      RENAME_SET_VALUE GemiddeldElektriciteitsverbruik_5 > GemiddeldElektriciteitsverbruik_kWh
      RENAME_SET_VALUE Stadsverwarming_6 > Stadsverwarming_perc
      RENAME_SET_VALUE IndelingswijzigingWijkenEnBuurten_7 > IndelingswijzigingWijkenEnBuurten
    -> AttributeValueMapper
AttributeValueMapper
    DIRECTION = Forward (Source To Destination)
    LUT = a,Totaal woningen,b,Appartement,c,Tussenwoning,d,Hoekwoning,e,Twee-onder-één-kap woning,f,Vrijstaande woning,g,Eigen woning,h,Huurwoning
    SRC = Woningkenmerken
    VAL_ATTR = Woningkenmerken_label
    -> AttributeValueMapper_Output
