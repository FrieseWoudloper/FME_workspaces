FME workspace GemeentelijkeMonumenten.fmw

Parameters:
- DestDataset_XLSXW2 = ..\output\gemeentelijkemonumenten.xlsx   # Destination Microsoft Excel File
- DestDataset_SHAPE = ..\output   # Destination Esri Shape Folder
- List = monument{}   # List to explode
- SourceDataset_WFS = https://geodata.nationaalgeoregister.nl/bestuurlijkegrenzen/wfs?   # Source WFS (Web Feature Service) URL

Readers:
- WFS_1: WFS from $(SourceDataset_WFS)

Writers:
- XLSXW2_1: XLSXW2 to $(DestDataset_XLSXW2)
- SHAPE_1: SHAPE to $(DestDataset_SHAPE)

Note: GemeentelijkeMonumenten.fmw / Datum: 4 mei 2016 / Versie: 1.0 / Auteur: Willy Bakker / Omschrijving: Workspace voor het creëren van een shape- en Excel-bestand met gemeentelijke monumenten in de provincie Groningen op basis van informatie in Wikipedia / Parameters: / DestDataset_XLSXW2 - Output Excel-bestand / DestDataset_SHAPE - Output Shape-bestand
Note: Het komt regelmatig voor dat de workspace er uit klapt en je de melding 'Translation failed' krijgt. / Als je dan in het Translation Log kijkt, zie je onderstaande regels. Blijkbaar gaat er iets mis met het inlezen van de respons van de bestuurlijke grenzen service. / Als je de workspace nog een keer uitvoert, gaat het meestal goed. / 2016-05-04 10:51:00| 9.7| 0.0|ERROR |XML Parser error: 'Error in input dataset:'https://geodata.nationaalgeoregister.nl:443/bestuurlijkegrenzen/wfs?SERVICE=WFS&VERSION=1.1.0&REQUEST=GetFeature&TYPENAME=bestuurlijkegrenzen%3Aprovincies&NAMESPACE=xmlns%28bestuurlijkegrenzen%3Dhttp%3A%2F%2Fbestuurlijkegrenzen.geonovum.nl%29&MAXFEATURES=30000' line:1 column:1786397 message:input ended before all started tags were ended; last tag started is 'gml:posList'' / 2016-05-04 10:51:00| 9.7| 0.0|ERROR |The XML Module halted on error, see the logfile for details

Bookmark: Gemeentenamen en CBS-codes bepalen
Note: PDOK-service bestuurlijke grenzen
provincies (reader WFS_1)
    attributes: gml_parent_id xml_buffer, gml_parent_property xml_buffer, gml_id xml_buffer, gid xml_int32, gid.xsi_nil xml_boolean, provincienaam xml_buffer, provincienaam.xsi_nil xml_boolean, geom xml_geometry
    -> TestFilter
Note: Alleen de provincie Groningen selecteren
TestFilter
    TEST_LIST = BOOL_OP,OR,COMPOSITE_TEST,<Unused>,TEST_CLAUSE,"TEST @Value(provincienaam) = Groningen",@Value(provincienaam) = Groningen
    DEFAULT_VALUE = <UNFILTERED>
    @Value(provincienaam) = Groningen -> FeatureReader
Note: Alleen Groninger gemeenten selecteren
FeatureReader
    WFS_DISABLE_AUTOMATIC_READER_TYPE_SELECTION = NO
    WFS_MAP_PREDEFINED_GML_PROPERTIES = NO
    WFS_USE_SEARCH_ENVELOPE = NO
    FORMAT = WFS
    WFS_MAX_RESULT_FEATURES = 30000
    INTERACT = Contains
    FEATURETYPES = gemeenten
    WFS_LOCAL_CACHE_EXPIRY = 60
    WFS_XML_FRAGMENTS_AS_DOCUMENTS = YES
    WFS_DISABLE_XML_NAMESPACE_PROCESSING = NO
    WFS_USE_OLD_READER = NO
    WFS_FLATTEN_XML_FRAGMENTS = NO
    WFS_MAP_GEOMETRY_COLUMNS = YES
    WFS_MAP_COMPLEX_PROPERTIES_AS = Nested Attributes
    WFS_ENFORCE_PATH_CONTINUITY_BY = SNAPPING_END_POINTS
    WFS_PREFERRED_VERSION = 1.1.0
    WFS_PREFER_POST = No
    WFS_USE_HTTP_AUTH = NO
    WFS_MAP_EMBEDDED_OBJECTS_AS = ATTRIBUTES
    FEATURETYPES_RADIO = FEATURETYPES
    WFS_USE_PROXY_SERVER = NO
    WFS_CLIP_TO_ENVELOPE = NO
    ATTR_ACCUM_MODE = Only Use Result
    ATTRIBUTES = gemeenten,"gml_parent_id,gml_id,gid,gid.xsi_nil,code,code.xsi_nil,gemeentenaam,gemeentenaam.xsi_nil,geom,fme_geometry{0},fme_geometry{1},fme_geometry{2},fme_geometry{3},fme_geometry{4},fme_geometry{5},fme_geometry{6},fme_geometry{7}"
    DATASET = https://geodata.nationaalgeoregister.nl/bestuurlijkegrenzen/wfs?
    COMBINE_GEOM = Use Result
    gemeenten -> AttributeKeeper
AttributeKeeper
    KEEP_ATTRS = gemeentenaam,code
    -> GeometryRemover
Note: Alleen gemeentenaam en CBS-code bewaren
GeometryRemover
    -> CoordinateSystemRemover
Note: EPSG:28992 verwijderen
CoordinateSystemRemover
    -> HTTPCaller

Bookmark: Wikipedia Heritage API bevragen en XML-respons inlezen
Note: Wikipedia Heritage API bevragen per gemeente
HTTPCaller
    USE_COOKIES = No
    STATUS_CODE_ATTR = _http_status_code
    HTTP_METHOD = GET
    TRANSFER_TIMEOUT_LENGTH = 90
    TARGET_ATTR_ENCODING = auto-detect
    ADDITIONAL_URL_PARAMETERS = action;search srcountry;nl-gem srmunicipality;%@Value(gemeentenaam)% format;XML limit;10000
    FOLLOW_REDIRECTS = Yes
    TARGET_URL = http://tools.wmflabs.org/heritage/api/api.php?
    ERROR_ATTR = _error
    VERIFY_SSL_CERTIFICATES = Yes
    RESPONSE_HEADER_LIST_ATTR = _headers
    TARGET_ATTR = _response_body
    SAVE_FILE = Attribute
    CONNECTION_TIMEOUT_LENGTH = 60
    -> XMLFlattener
Note: <Monument> tags uit XML-respons filteren
XMLFlattener
    FEATURE_TYPES_FORMAT_NAME = XML
    EMBEDDED_EXPRESSIONS = monuments
    ATTRIBUTE_XML = _response_body
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> ListExploder
ListExploder
    LIST_ATTR = $(List)
    INDEX_ATTR = _element_index
    ATTR_ACCUM_MODE = Merge Incoming List
    ATTR_CONFLICT_RES = Use Original
    LIST_FOUND -> AttributeExposer
    NOT_FOUND -> BulkAttributeRenamer
Note: Naamgevingen attributen van gemeenten met 0 of 1 monument aanpassen
BulkAttributeRenamer
    CASE_DISP = yes
    REPLACE_STR = monument.
    ATTRCHOICE = All Attributes
    PATTERN_ACTION_DISP = Remove Prefix String
    -> AttributeExposer
AttributeExposer
    ATTR_LIST = country,lang,id,adm0,adm1,adm2,adm3,adm4,name,address,municipality,lat,lon,image,commonscat,source,monument_article,registrant_url,changed
    -> TestFilter_2

Bookmark: Clean-up
Note: Rijen met gemeenten zonder monumenten verwijderen
TestFilter_2
    TEST_LIST = BOOL_OP,OR,COMPOSITE_TEST,<Unused>,TEST_CLAUSE,"TEST id ATTRIBUTE_IS_MISSING """"",id ATTRIBUTE_IS_MISSING
    DEFAULT_VALUE = <UNFILTERED>
    <UNFILTERED> -> StringReplacer
Note: MediaWiki tags verwijderen
StringReplacer
    REGEXP = yes
    CASE = no
    FIND_TEXT = \{\{[^\|]+\|[^\|]+\|||\}\}||\[\[[^\|]+\|||\[\[||\]\]
    NO_MATCH = _FME_NO_OP_
    SRC_ATTRS = address,adm2,municipality,name
    -> StringReplacer_2
Note: HTML-tags verwijderen
StringReplacer_2
    REGEXP = yes
    CASE = no
    FIND_TEXT = <br[\s]*/>
    NO_MATCH = _FME_NO_OP_
    SRC_ATTRS = address,name
    -> StringReplacer_3
Note: 'No break spaces' verwijderen
StringReplacer_3
    REGEXP = no
    CASE = no
    FIND_TEXT = &nbsp;
    NO_MATCH = _FME_NO_OP_
    SRC_ATTRS = address,name
    REPLACE_TEXT = " "
    -> AttributeCreator
Note: URL's aanvullen
AttributeCreator
    ATTR_LIST = image,"FME_CONDITIONAL:DEFAULT_VALUE'http://commons.wikimedia.org/wiki/File:@Value(image)#/media/File:@Value(image)'BOOL_OP;OR;COMPOSITE_TEST;<Unused>;TEST image ATTRIBUTE_IS_EMPTY _FME_BLANK_STRING_'@Value(image)'FME_NUM_CONDITIONS2___",source,"FME_CONDITIONAL:DEFAULT_VALUE'http:@Value(source)'BOOL_OP;OR;COMPOSITE_TEST;<Unused>;TEST source ATTRIBUTE_IS_EMPTY _FME_BLANK_STRING_'@Value(source)'FME_NUM_CONDITIONS2___"
    -> AttributeRemover
AttributeRemover
    REMOVE_ATTRS = _element_index,_http_status_code,_response_body
    LIST_ATTRS = _headers{} _headers{}.name _headers{}.value
    -> DuplicateRemover
Note: Dubbele rijen verwijderen
DuplicateRemover
    KEYATTR = address adm0 adm1 adm2 adm3 adm4 changed commonscat country id image lang lat lon monument_article municipality name registrant_url source
    UNIQUE -> TestFilter_3

Bookmark: Punt-geometrie maken en X/Y in Rijksdriehoekstelsel bepalen
Note: Rijen zonder missende lat- of lon-waarden selecteren
TestFilter_3
    TEST_LIST:
      BOOL_OP,OR,COMPOSITE_TEST,<Unused>,TEST_CLAUSE,"TEST lat ATTRIBUTE_IS_EMPTY """"
      TEST lon ATTRIBUTE_IS_EMPTY """"",lat ATTRIBUTE_IS_EMPTY
    DEFAULT_VALUE = <UNFILTERED>
    lat ATTRIBUTE_IS_EMPTY -> AttributeKeeper_2
    <UNFILTERED> -> VertexCreator
Note: Punt-geometrie maken
VertexCreator
    MODE_NAME = Add Point
    XVAL = @Value(lon)
    INDEX = 0
    YVAL = @Value(lat)
    -> Reprojector
Note: EPSG:4326 (WGS84) omzetten naar EPSG:28992 (RD_new)
Reprojector
    DEST = EPSG:28992
    RASTER_CELL_SIZE = Preserve Cells
    SOURCE = LL-WGS84
    INTERPOLATION_TYPE_NAME = Nearest Neighbor
    REPROJECTED -> CoordinateExtractor
Note: x- en y-coördinaat als attribuut toevoegen
CoordinateExtractor
    Z_DEFAULT = -9999
    X_ATTR = x
    IND = 0
    Y_ATTR = y
    Z_ATTR = z
    -> AttributeCreator_2
AttributeCreator_2
    ATTR_LIST = x,@round(@Value(x)),y,@round(@Value(y))
    -> HTTPCaller_2

Bookmark: Woonplaats toevoegen m.b.v. BAG-service
Note: Per rij woonplaats opvragen uit de BAG
HTTPCaller_2
    USE_COOKIES = No
    STATUS_CODE_ATTR = _http_status_code
    HTTP_METHOD = GET
    TRANSFER_TIMEOUT_LENGTH = 90
    TARGET_ATTR_ENCODING = auto-detect
    ADDITIONAL_URL_PARAMETERS = service;wfs version;2.0.0 request;GetFeature typeName;bag:woonplaats cql_filter;intersects(bag:geometrie,point(@Value(x) @Value(y)))
    FOLLOW_REDIRECTS = Yes
    TARGET_URL = http://geodata.nationaalgeoregister.nl/bag/wfs?
    ERROR_ATTR = _error
    VERIFY_SSL_CERTIFICATES = Yes
    RESPONSE_HEADER_LIST_ATTR = _headers
    TARGET_ATTR = _response_body
    SAVE_FILE = Attribute
    CONNECTION_TIMEOUT_LENGTH = 60
    -> XMLFlattener_2
XMLFlattener_2
    FEATURE_TYPES_FORMAT_NAME = XML
    EMBEDDED_EXPRESSIONS = bag:woonplaats
    ATTRIBUTE_XML = _response_body
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> AttributeExposer_2
AttributeExposer_2
    ATTR_LIST = woonplaats
    -> AttributeRemover_3
AttributeRemover_3
    REMOVE_ATTRS = _http_status_code,_response_body
    LIST_ATTRS = _headers{} _headers{}.name _headers{}.value
    -> AttributeKeeper_2

Bookmark: Shape en Excel-bestand aanmaken
AttributeKeeper_2
    KEEP_ATTRS = address,code,gemeentenaam,id,image,name,source,x,y,woonplaats
    -> AttributeRenamer
AttributeRenamer
    ATTR_LIST = name,omschrijving,,address,adres,,gemeentenaam,gemeente,,code,CBS-code,,image,afbeelding,,source,bron,,id,id-wikipedia,
    -> Gemeentelijke monumenten (writer XLSXW2_1)
    -> GemeentelijkeMonumenten (writer SHAPE_1)
Note: Shape-bestand
GemeentelijkeMonumenten (writer SHAPE_1)
    attributes: OMSCHR char(200), ADRES char(200), WOONPLAATS char(200), GEMEENTE char(200), CBS_CODE char(200), ID_WIKI char(200), AFBEELDING char(200), BRON char(200), X char(200), Y char(200)
Note: Excel-bestand
Gemeentelijke monumenten (writer XLSXW2_1)
    attributes: omschrijving auto(20,format_type;Simple;font_type;;font_color;;fill_color;;custom_options;;text_wrap;no), adres auto(20,format_type;Simple;font_type;;font_color;;fill_color;;custom_options;;text_wrap;no), woonplaats auto(20,format_type;Simple;font_type;;font_color;;fill_color;;custom_options;;text_wrap;no), gemeente auto(20,format_type;Simple;font_type;;font_color;;fill_color;;custom_options;;text_wrap;no), CBS-code auto(20,format_type;Simple;font_type;;font_color;;fill_color;;custom_options;;text_wrap;no), afbeelding auto(20,format_type;Simple;font_type;;font_color;;fill_color;;custom_options;;text_wrap;no), id-wikipedia auto(20,format_type;Simple;font_type;;font_color;;fill_color;;custom_options;;text_wrap;no), bron auto(20,format_type;Simple;font_type;;font_color;;fill_color;;custom_options;;text_wrap;no), x auto(20,format_type;Simple;font_type;;font_color;;fill_color;;custom_options;;text_wrap;no), y auto(20,format_type;Simple;font_type;;font_color;;fill_color;;custom_options;;text_wrap;no)
