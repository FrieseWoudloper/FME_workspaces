FME workspace GemeentelijkeMonumenten_Itay.fmw
Title: Wikipedia monuments API
Description: This workspace uses the Wikipedia API (http://tools.wmflabs.org/heritage/api/api.php?) in combination with the BAG service from the Dutch SDI (PODK). 
    Point features in ESPG 28992 are created and written to ESRI shapefile and Microsoft excel.
Usage: The workspace uses an online XLS input with provice and municipalities names.
    A selection is made in the TestFeilter transformer. 
        Adjust the selection for your needs.
    Select the location for the output files by changing the destination locations.
Requirements: FME 2016.1
History: Unknown,Willy Bakker,Original implementation,May 2016,Itay Bar-on,Version 1

Parameters:
- DestDataset_XLSXW = C:/   # Destination Microsoft Excel File
- DestDataset_ESRISHAPE = C:/   # Destination Esri Shapefile Folder
- List = monument{}   # List to explode
- SourceDataset_XLSXR = https://www.cbs.nl/-/media/imported/onze%20diensten/methoden/classificaties/documents/2014/43/gemeenten%20alfabetisch%20per%20provincie%202015.xls   # Source Microsoft Excel File(s)

Readers:
- XLSXR_1: XLSXR from $(SourceDataset_XLSXR)

Writers:
- XLSXW_1: XLSXW to $(DestDataset_XLSXW)
- ESRISHAPE_1: ESRISHAPE to $(DestDataset_ESRISHAPE) in EPSG:28992

Note: Workspace details: / This workspace uses the Wikipedia API (http://tools.wmflabs.org/heritage/api/api.php?) in combination with the BAG service from the Dutch SDI (PDOK). / Point features in EPSG 28992 are created and written to ESRI shapefile and Microsoft excel. / Workspace use: / The workspace uses an online XLS input with provice and municipalities names. / A selection is made in the TestFeilter transformer. / Adjust the selection for your needs. / Select the location for the output files by changing the destination locations.
Note: CBS Online XLS
Gemeenten_alfabetisch_per_provi/Gemeenten_alfabetisch_per_provincie_2015 (reader XLSXR_1)
    attributes: Gemeentecode number(5,0), Provinciecode number(3,0), Gemeentenaam char(31), Provincienaam char(14)
    -> TestFilter
Note: Test for province name / Adjust for your needs
TestFilter
    TEST_LIST = BOOL_OP,OR,COMPOSITE_TEST,<Unused>,TEST_CLAUSE,"TEST @Value(Provincienaam) = Groningen",Groningen
    DEFAULT_VALUE = <UNFILTERED>
    Groningen -> HTTPCaller_API

Bookmark: Get Data
HTTPCaller_API
    TARGET_ATTR = _response_body
    TARGET_URL = http://tools.wmflabs.org/heritage/api/api.php?
    TRANSFER_TIMEOUT_LENGTH = 90
    USE_COOKIES = No
    VERIFY_SSL_CERTIFICATES = Yes
    FOLLOW_REDIRECTS = Yes
    HTTP_METHOD = GET
    ADDITIONAL_URL_PARAMETERS = action;search srcountry;nl-gem srmunicipality;%@Value(Gemeentenaam)% format;XML limit;10000
    ERROR_ATTR = _error
    RESPONSE_HEADER_LIST_ATTR = _headers
    TARGET_ATTR_ENCODING = fme-system
    STATUS_CODE_ATTR = _http_status_code
    SAVE_FILE = Attribute
    CONNECTION_TIMEOUT_LENGTH = 60
    -> XMLFragmenter
XMLFragmenter
    EMBEDDED_EXPRESSIONS = monuments
    ATTRIBUTE_XML = _response_body
    MERGE_ATTRS = Yes
    NEW_ATTRIBUTES = monument{} lat lon address name image source id
    FEATURE_TYPES_FORMAT_NAME = XML
    XML_SOURCE_TYPE = Attribute with XML document
    FLATTEN_OPTIONS = <structure separator="." map-empty-elements="yes" matched-prefix="attributes" matched-attributes="yes" cardinality="+{?}" structure-prefix="" child-position-attribute="" except-expression="" ui-mode="basic" matched-ancestor-attributes="parent"/>
    FRAGMENTS -> ListExploder
ListExploder
    ATTR_ACCUM_MODE = Merge Incoming List
    ATTR_CONFLICT_RES = Use Original
    LIST_ATTR = monument{}
    INDEX_ATTR = _element_index
    LIST_FOUND -> DuplicateFilter
    NOT_FOUND -> DuplicateFilter

Bookmark: Clean data
DuplicateFilter
    INPUT_ORDERED_CHOICE = No
    KEYATTR = lat address lon
    UNIQUE -> BulkAttributeRemover
BulkAttributeRemover
    ATTR_EXP = _headers*|xml*|_response*
    -> AttributeSplitter

Bookmark: Select address
AttributeSplitter
    DELIMITER = |
    DROP_EMPTY_PARTS = No
    LIST_NAME = _list
    TRIM_OPTION = Both
    ATTR_NAME = address
    -> ListElementCounter
ListElementCounter
    LIST_NAME = _list{}
    CNT_ATTR = _element_count
    -> ListIndexer
ListIndexer
    INDEX = @Value(_element_count)-1
    PREFIX = Adres
    LIST_ATTR = _list{}
    -> StringReplacer

Bookmark: Clean address
StringReplacer
    FIND_TEXT = \{\{[^\|]+\|[^\|]+\|||\}\}||\[\[[^\|]+\|||\[\[||\]\]|<br[\s]*/>|&nbsp;
    NO_MATCH = _FME_NO_OP_
    REGEXP = YES
    SRC_ATTRS = name,Adres_list
    CASE = NO
    -> AttributeReprojector

Bookmark: WPL
AttributeReprojector
    SOURCE = EPSG:4326
    DEST = EPSG:28992
    YATTR = lat
    XATTR = lon
    -> HTTPCaller_wplWPL
HTTPCaller_wplWPL
    TARGET_ATTR = _response_body
    TARGET_URL = http://geodata.nationaalgeoregister.nl/bag/wfs?
    TRANSFER_TIMEOUT_LENGTH = 90
    USE_COOKIES = No
    VERIFY_SSL_CERTIFICATES = Yes
    FOLLOW_REDIRECTS = Yes
    HTTP_METHOD = GET
    ADDITIONAL_URL_PARAMETERS = service;wfs version;2.0.0 request;GetFeature typeName;bag:woonplaats cql_filter;intersects(bag:geometrie,point(@Value(lon) @Value(lat)))
    ERROR_ATTR = _error
    RESPONSE_HEADER_LIST_ATTR = _headers
    TARGET_ATTR_ENCODING = auto-detect
    STATUS_CODE_ATTR = _http_status_code
    SAVE_FILE = Attribute
    CONNECTION_TIMEOUT_LENGTH = 60
    -> XMLFlattener_WPL
XMLFlattener_WPL
    EMBEDDED_EXPRESSIONS = bag:woonplaats
    ATTRIBUTE_XML = _response_body
    NEW_ATTRIBUTES = woonplaats
    FEATURE_TYPES_FORMAT_NAME = XML
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> AttributeRemover

Bookmark: Result attributes
AttributeRemover
    LIST_ATTRS = _headers{} _headers{}.name _headers{}.value _list{}
    -> AttributeManager
AttributeManager
    ATTR_TABLE:
      REMOVE Gemeentecode
      REMOVE Provinciecode
      RENAME_SET_VALUE Gemeentenaam > Gemeente
      RENAME_SET_VALUE Provincienaam > Provincie
      REMOVE _http_status_code
      REMOVE monument
      RENAME_SET_VALUE name > Omschrijving
      RENAME_SET_VALUE image > Afbeelding
      RENAME_SET_VALUE source > Bron
      RENAME_SET_VALUE id > ID-wikipedia
      RENAME_SET_VALUE Adres_list > Adres
      RENAME_SET_VALUE woonplaats > Woonplaats
      REMOVE address
      REMOVE _element_index
      REMOVE _element_count
      REMOVE _response_body
    -> Output
    -> Monumenten (writer XLSXW_1)
    -> VertexCreator
VertexCreator
    YVAL = @Value(lat)
    MODE_NAME = Add Point
    XVAL = @Value(lon)
    -> Monumenten (writer ESRISHAPE_1)

Bookmark: Output XLS \ SHP
Output: Inspector [off]
Monumenten (writer XLSXW_1)
    attributes: ID-wikipedia auto(20), Adres auto(20), Woonplaats auto(20), Gemeente auto(20), Provincie auto(20), Omschrijving auto(20), Afbeelding auto(20), Bron auto(20)
Monumenten (writer ESRISHAPE_1)
    attributes: ID_wikiped char(200), Adres char(200), Woonplaats char(200), Gemeente char(200), Provincie char(200), Omschrijvi char(200), Afbeelding char(200), Bron char(200)
