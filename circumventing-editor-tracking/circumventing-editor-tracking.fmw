FME workspace circumventing-editor-tracking.fmw

Parameters:
- username =
- password =
- root_url = https://www.arcgis.com/sharing/rest   # Root-URL
- feature_server = https://services6.arcgis.com/A4kymGAyIDZ27uZU/arcgis/rest/services/Testing_temporarily_disabling_editor_tracking/FeatureServer   # Feature Server URL
- feature_server_admin = https://services6.arcgis.com/A4kymGAyIDZ27uZU/arcgis/rest/admin/services/Testing_temporarily_disabling_editor_tracking/FeatureServer   # Feature Server Admin URL

Creator
    GEOMTYPE = Geometry Object
    NUM = 1
    CREATED -> HTTPCaller
Decelerator
    DECEL_TYPE = Per Feature Delay
    DELAY = 10
    -> HTTPCaller_3
Decelerator_2
    DECEL_TYPE = Per Feature Delay
    DELAY = 10
    -> HTTPCaller_4

Bookmark: Get token
HTTPCaller
    CONNECTION_TIMEOUT_LENGTH = 60
    ERROR_ATTR = _error
    FOLLOW_REDIRECTS = Yes
    HTTP_METHOD = POST
    MULTIPARTS = username StringUpload SOURCE_EXPRESSION;$(username);MIME_TYPE;text/plain;FME_CONTROLLER_QUERY_FILE;transformers\dependencies\http\StringUpload.fme password StringUpload SOURCE_EXPRESSION;$(password);MIME_TYPE;text/plain;FME_CONTROLLER_QUERY_FILE;transformers\dependencies\http\StringUpload.fme referer StringUpload SOURCE_EXPRESSION;http://provgroningen.maps.arcgis.com;MIME_TYPE;text/plain;FME_CONTROLLER_QUERY_FILE;transformers\dependencies\http\StringUpload.fme f StringUpload SOURCE_EXPRESSION;json;MIME_TYPE;text/plain;FME_CONTROLLER_QUERY_FILE;transformers\dependencies\http\StringUpload.fme
    SAVE_FILE = Attribute
    STATUS_CODE_ATTR = _http_status_code
    TARGET_ATTR = _response_body
    TARGET_ATTR_ENCODING = auto-detect
    TARGET_URL = $(root_url)/generateToken
    TRANSFER_TIMEOUT_LENGTH = 90
    UPLOAD_TYPE = Multipart / Form Data
    USE_COOKIES = No
    VERIFY_SSL_CERTIFICATES = No
    -> JSONExtractor
JSONExtractor
    EXTRACT_QUERY_TABLE = token json["token"]
    JSON_DOCUMENT = @Value(_response_body)
    EVALUATED -> HTTPCaller_2

Bookmark: Disable editor tracking
HTTPCaller_2
    CONNECTION_TIMEOUT_LENGTH = 60
    ERROR_ATTR = _error
    FOLLOW_REDIRECTS = Yes
    HTTP_METHOD = POST
    MULTIPARTS = async StringUpload SOURCE_EXPRESSION;true;MIME_TYPE;text/plain;FME_CONTROLLER_QUERY_FILE;transformers\dependencies\http\StringUpload.fme f StringUpload SOURCE_EXPRESSION;json;MIME_TYPE;text/plain;FME_CONTROLLER_QUERY_FILE;transformers\dependencies\http\StringUpload.fme token StringUpload SOURCE_EXPRESSION;@Value(token);MIME_TYPE;text/plain;FME_CONTROLLER_QUERY_FILE;transformers\dependencies\http\StringUpload.fme updateDefinition StringUpload SOURCE_EXPRESSION;{"editorTrackingInfo":{"enableEditorTracking":false}};MIME_TYPE;application/json;FME_CONTROLLER_QUERY_FILE;transformers\dependencies\http\StringUpload.fme
    SAVE_FILE = Attribute
    STATUS_CODE_ATTR = _http_status_code
    TARGET_ATTR = _response_body
    TARGET_ATTR_ENCODING = auto-detect
    TARGET_URL = $(feature_server_admin)/updateDefinition
    TRANSFER_TIMEOUT_LENGTH = 90
    UPLOAD_TYPE = Multipart / Form Data
    USE_COOKIES = No
    VERIFY_SSL_CERTIFICATES = No
    -> Decelerator

Bookmark: Apply edits
HTTPCaller_3
    CONNECTION_TIMEOUT_LENGTH = 60
    ERROR_ATTR = _error
    FOLLOW_REDIRECTS = Yes
    HTTP_METHOD = POST
    MULTIPARTS = f StringUpload SOURCE_EXPRESSION;json;MIME_TYPE;text/plain;FME_CONTROLLER_QUERY_FILE;transformers\dependencies\http\StringUpload.fme token StringUpload SOURCE_EXPRESSION;@Value(token);MIME_TYPE;text/plain;FME_CONTROLLER_QUERY_FILE;transformers\dependencies\http\StringUpload.fme updates StringUpload SOURCE_EXPRESSION;[{ "attributes" : {"OBJECTID" : 1, "DESCRIPTION" : "church"}},{ "attributes" : {"OBJECTID" : 2, "DESCRIPTION" : "tower"}},{ "attributes" : {"OBJECTID" : 3, "DESCRIPTION" : "school"}}];MIME_TYPE;application/json;FME_CONTROLLER_QUERY_FILE;transformers\dependencies\http\StringUpload.fme
    SAVE_FILE = Attribute
    STATUS_CODE_ATTR = _http_status_code
    TARGET_ATTR = _response_body
    TARGET_ATTR_ENCODING = auto-detect
    TARGET_URL = $(feature_server)/0/applyEdits
    TRANSFER_TIMEOUT_LENGTH = 90
    UPLOAD_TYPE = Multipart / Form Data
    USE_COOKIES = No
    VERIFY_SSL_CERTIFICATES = No
    -> Decelerator_2

Bookmark: Enable editor tracking
HTTPCaller_4
    CONNECTION_TIMEOUT_LENGTH = 60
    ERROR_ATTR = _error
    FOLLOW_REDIRECTS = Yes
    HTTP_METHOD = POST
    MULTIPARTS = async StringUpload SOURCE_EXPRESSION;true;MIME_TYPE;text/plain;FME_CONTROLLER_QUERY_FILE;transformers\dependencies\http\StringUpload.fme f StringUpload SOURCE_EXPRESSION;json;MIME_TYPE;text/plain;FME_CONTROLLER_QUERY_FILE;transformers\dependencies\http\StringUpload.fme token StringUpload SOURCE_EXPRESSION;@Value(token);MIME_TYPE;text/plain;FME_CONTROLLER_QUERY_FILE;transformers\dependencies\http\StringUpload.fme updateDefinition StringUpload SOURCE_EXPRESSION;{"editorTrackingInfo":{"enableEditorTracking":true}};MIME_TYPE;application/json;FME_CONTROLLER_QUERY_FILE;transformers\dependencies\http\StringUpload.fme
    SAVE_FILE = Attribute
    STATUS_CODE_ATTR = _http_status_code
    TARGET_ATTR = _response_body
    TARGET_ATTR_ENCODING = auto-detect
    TARGET_URL = $(feature_server_admin)/updateDefinition
    TRANSFER_TIMEOUT_LENGTH = 90
    UPLOAD_TYPE = Multipart / Form Data
    USE_COOKIES = No
    VERIFY_SSL_CERTIFICATES = No
